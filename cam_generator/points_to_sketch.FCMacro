import FreeCAD as App
import Part
import Sketcher
import os.path
import numpy as np

# File format should be :
#	0.0 0.23 0.0
#	1.234 3.456 0.0
#	0.45 2.4567 0.0
#	.... ....

# Define a filename.
FILENAME = r"C:\Users\vigno\Documents\Cours\Keio\MT\dev\cam_generator\cam.txt"

#Get points list from specified file
pt_list = []

if not os.path.isfile(FILENAME):
    print('File does not exist.')
else:
    with open(FILENAME) as f:
        for line in f.readlines():
            pt = [float(i) for i in line.split(" ")]
            pt_list.append(pt)

# Create doc and add points to a new skecth
doc = App.newDocument()  

sketch = doc.addObject("Sketcher::SketchObject", "Sketch")

for i,pt in enumerate(pt_list[:-1]):
	sketch.addGeometry(Part.LineSegment(App.Vector(pt[0], pt[1], pt[2]),
                                    App.Vector(pt_list[i+1][0], pt_list[i+1][1], pt_list[i+1][2])), False)

doc.recompute()
